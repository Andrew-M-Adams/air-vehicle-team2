# Table_of_Requirements

## Table_of_Requirements!Requirements: References to Table_of_Requirements.xlsx (Requirements) (Container)
Read-only references to Microsoft Excel document.
- srcFileChecksum: 66DC101D257A5C7DB0CB08610A599C89

### 1: Cost (Functional)
The aircraft must be extremely affordable, or cannot be manufactured due to strict budgetary constraints.

### 2: Manufacturing (Functional)
There shall be a minimum number of aircraft produced

### 3: Structures (Functional)
The aircraft must have specific design load factors in clean configuration with 50% internal fuel

### 4: Structures (Functional)
Aircraft must withstand a dynamic pressure of 2133 psf when flying at Mach 1.2 at sea level

### 5: Structures (Functional)
Aircraft must have a safety factor on all loads

### 6: Structures (Functional)
The aircraft must have a minimum design service life

### 7: Stability and Control (Functional)
The aircraft must have a static margin less than or equal to 10%.

### 8: Mission Performance (Functional)
The aircraft must perform over the Intercept Mission Radius

### 9: Mission Performance (Functional)
The aircraft must perform over DCA Mission CAP endurance at 300 nm radius

### 10: Performance (Functional)
The aircraft must reach a specific maximum mach number at maneuver weight (50% internal fuel)

### 11: Performance (Functional)
Aircraft must be able to takeoff and land at any NATO runway

### 12: Aircraft Systems (Functional)
The aircraft must have remote pilot capability

### 13: Aircraft Systems (Functional)
Fuel tanks must be self-healing

### 14: Project Deadline (Functional)
The engine selected for the aircraft must be in production or forcast to be in production

### 15: Aircraft Systems (Functional)
Electrical and hydraulic systems power requirement

### 16: Aircraft Systems (Functional)
Environmental control systems and avionics liquid cooling system % of engine mass flow

### 17: Payload (Functional)
The aircraft must have air-to-air weapons systems

### 18: Stability and Control (Functional)
The aircraft must have a phugoid mode damping ratio less than or equal to .04.

### 19: Stability and Control (Functional)
The aircraft must have a short period mode damping ratio less than or equal to 2.0 and greater than or equal to 0.3.

### 20: Stability and Control (Functional)
The aircraft must have a roll subsidence mode period less than or equal to 1.4 seconds.

### 21: Stability and Control (Functional)
The aircraft must have a spiral mode period greater than or equal to 20 seconds.

### 22: Stability and Control (Functional)
The aircraft must have a dutch roll mode damping ratio greater than or equal to 0.08.

### 23: Stability and Control (Functional)
The static longitudinal (pitch) stability derivative must be less than 0.

### 24: Stability and Control (Functional)
The static lateral (roll) stability derivative must be less than zero.

### 25: Stability and Control (Functional)
The static directional (yaw) stability derivative must be greater than zero.

### 26: Stability and Control (Functional)
The roll damping derivative should be less than zero for roll-handling qualities.

### 27: Stability and Control (Functional)
The pitch damping derivative should be less than zero in order to meet short period damping requirements.

### 28: Mission Systems (Functional)
Latency of displayed confirmation of action between UAS and operator doesn't exceed stated value for both Vehicle Motion Control and Weapon System Control

### 29: Performance (Functional)
The aircraft has to have an instantanious turn rate of 18 °/s at 35,000 ft.

### 30: Mission Systems (Functional)
Provides alerts from internal sensors for all conditions listed in Table XXXV

### 31: Mission Systems (Functional)
Contains internal sesnors detailing all vehicle state paramaters for use of pilot in Table XXXVII

### 32: Mission Systems (Functional)
Contains capability to automatically "return home" to launch base when position is lost for a specified amount of time.

### 33: Mission Systems (Functional)
Contains capability to automatically activate "kill switch" when communications are lost for a specified amount of time.

### 34: Mission Systems (Functional)
Contains emergency transponder hardware to determine location of vehicle when communications are lost.

### 35: Safety (Functional)
Aircraft must be capable of take-off and landing on icy runway

### 36: Aerodynamics (Functional)
The vehicles AR must be smaller or equal to 5.

### 37: ConOps (Functional)
Aircraft shall have the abillity to receive commands from F-22 and/or F-35 pilots.

### 38: ConOps (Functional)
Aircraft must be able to receive targeting data from F-22 and/or F-35.

### 39: ConOps (Functional)
Aircraft shall have in-air refueling capabilities.

### 40: ConOps (Functional)
Aircraft shall be able to provide visiual of target within 40 nm.

### 41: ConOps (Functional)
Aircraft shall have both static countermeasure and Electronic Countermeasure (ECM) systems
